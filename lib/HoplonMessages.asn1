HoplonMessages DEFINITIONS AUTOMATIC TAGS ::= BEGIN

EXPORTS Person, Package, Verdict, Audit, SignedAudit, SignedAudits;

Person ::= [19] SEQUENCE {

        name UTF8String,
        location INTEGER {home(0),field(1),roving(2)},
        age INTEGER OPTIONAL }


-- TODO: add size restrictions to (all?) strings

Package ::= [0] SEQUENCE {
  -- "hexpm" seems to be the identifier mix uses in mix.lock
  ecosystem UTF8String DEFAULT "hexpm",
  name UTF8String,
  -- the version number, like "1.0.0-rc3"
  -- NOTE if this was PrintableString, Erlang would decode it to a charlist
  version UTF8String,
  -- the hash of the package version, like
  -- "3c7b0f02851f5fc13b040e8e925051452e41248f685e40250d7e40b07b9f8c10"
  hash UTF8String,
  ...
}

Verdict ::= [1] ENUMERATED {
  dangerous,
  suspicious,
  lgtm,
  safe,
  ...
}

Audit ::= [2] SEQUENCE {
  package Package,
  verdict Verdict OPTIONAL,
  comment UTF8String OPTIONAL,
  publicKeyFingerprint UTF8String,
  -- Unix TIME
  createdAt INTEGER,
  -- is the person creating the audit the author of the package?
  auditedByAuthor BOOLEAN,
  ...
}

SignedAudit ::= [3] SEQUENCE {
  audit Audit,
  signature OCTET STRING
}

SignedAudits ::= SEQUENCE OF SignedAudit

END
